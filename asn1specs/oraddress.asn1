ORAddressModule	-- From MTSAbstractService { joint-iso-ccitt mhs(6) mts(3)
				-- modules(0) mts-abstract-service(1) version-1994 (0) }

DEFINITIONS IMPLICIT TAGS ::=

BEGIN

-- EXPORTS ALL --

IMPORTS
	PresentationAddress
		FROM SelectedAttributeTypes ;

ORAddress	::= --snacc isPdu:"TRUE" -- SEQUENCE {
    standardAttributes        StandardAttributes,
    domainDefinedAttributes   DomainDefinedAttributes OPTIONAL,
    extensionAttributes       ExtensionAttributes OPTIONAL }

StandardAttributes	::= SEQUENCE {
    countryName                  CountryName OPTIONAL,
    administrationDomainName     AdministrationDomainName OPTIONAL,
    networkAddress           [0] NetworkAddress OPTIONAL,
    terminalIdentifier       [1] TerminalIdentifier OPTIONAL,
    privateDomainName        [2] PrivateDomainName OPTIONAL,
    organizationName         [3] OrganizationName OPTIONAL,
    numericUserIdentifier    [4] NumericUserIdentifier OPTIONAL,
    personalName             [5] PersonalName OPTIONAL,
    organizationalUnitNames  [6] OrganizationalUnitNames OPTIONAL }

CountryName ::= [APPLICATION 1] CHOICE {
    x121DccCode        NumericString (SIZE (ub-country-name-numeric-length)),
    iso3166Alpha2Code  PrintableString (SIZE (ub-country-name-alpha-length)) }

AdministrationDomainName ::= [APPLICATION 2] CHOICE {
    numericString    NumericString (SIZE (0..ub-domain-name-length)),
    printableString  PrintableString (SIZE (0..ub-domain-name-length)) }

NetworkAddress ::= X121Address

X121Address ::= NumericString (SIZE (1..ub-x121-address-length))

TerminalIdentifier ::= PrintableString (SIZE (1..ub-terminal-id-length))

PrivateDomainName ::= CHOICE {
    numericString    NumericString (SIZE (0..ub-domain-name-length)),
    printableString  PrintableString (SIZE (0..ub-domain-name-length)) }

OrganizationName ::= PrintableString (SIZE (1..ub-organization-name-length))

NumericUserIdentifier ::= NumericString (SIZE (1..ub-numeric-user-id-length))

PersonalName ::= SET {
    surname					[0] PrintableString (SIZE(1..ub-surname-length)),
    given-name				[1] PrintableString (SIZE(1..ub-given-name-length)),
    initials				[2] PrintableString (SIZE(1..ub-initials-length)),
    generation-qualifier	[3] PrintableString (SIZE(1..ub-generation-qualifier-length))
							OPTIONAL }
 
OrganizationalUnitName ::= PrintableString 
                           (SIZE (1..ub-organizational-unit-name-length))

OrganizationalUnitNames ::= SEQUENCE SIZE (1..ub-organizational-units) OF
								OrganizationalUnitName

DomainDefinedAttributes ::= SEQUENCE SIZE (1..ub-domain-defined-attributes) OF
								DomainDefinedAttribute

DomainDefinedAttribute ::= SEQUENCE {
    type   PrintableString (SIZE (0..ub-domain-defined-attribute-type-length)),
    value  PrintableString (SIZE (0..ub-domain-defined-attribute-value-length)) }

ExtensionAttributes ::= SET SIZE (1..ub-extension-attributes) OF 
							ExtensionAttribute

ExtensionAttribute ::= SEQUENCE {
    extensionAttributeType   [0] INTEGER,
    extensionAttributeValue  [1] ANY DEFINED BY extensionAttributeType }

commonNameExtAttribute OBJECT-TYPE	-- EXTENSION-ATTRIBUTE
	SYNTAX	CommonName
	ACCESS	read-write
	STATUS	mandatory
	::= 1

CommonName	::= PrintableString (SIZE (1..ub-common-name-length))

teletexCommonNameExtAttribute OBJECT-TYPE	-- EXTENSION-ATTRIBUTE
	SYNTAX	TeletexCommonName
	ACCESS	read-write
	STATUS	mandatory
	::= 2

TeletexCommonName	::= TeletexString (SIZE (1..ub-common-name-length))

teletexOrganizationNameExtAttribute OBJECT-TYPE	-- EXTENSION-ATTRIBUTE
	SYNTAX	TeletexOrganizationalName
	ACCESS	read-write
	STATUS	mandatory
	::= 3

TeletexOrganizationalName	::= TeletexString (SIZE (1..ub-organization-name-length))

teletexPersonalNameExtAttribute OBJECT-TYPE	-- EXTENSION-ATTRIBUTE
	SYNTAX	TeletexPersonalName
	ACCESS	read-write
	STATUS	mandatory
	::= 4

TeletexPersonalName	::= SET {
	surname			[0] TeletexString (SIZE (1..ub-surname-length)),
	given-name		[1] TeletexString (SIZE (1..ub-given-name-length)) OPTIONAL,
	initials		[2] TeletexString (SIZE (1..ub-initials-length)) OPTIONAL,
	generation-qualifier	[3] TeletexString (SIZE (1..ub-generation-qualifier-length)) 
								OPTIONAL }

teletexOrganizationalUnitNamesExtAttribute OBJECT-TYPE	-- EXTENSION-ATTRIBUTE
	SYNTAX	TeletexOrganizationUnitNames
	ACCESS	read-write
	STATUS	mandatory
	::= 5

TeletexOrganizationUnitNames	::= SEQUENCE SIZE (1..ub-organizational-units) OF
										TeletexOrganizationalUnitName

TeletexOrganizationalUnitName	::= TeletexString (SIZE (1..ub-organizational-unit-name-length))

teletexDomainDefinedAttributesExtAttribute OBJECT-TYPE	-- EXTENSION-ATTRIBUTE
	SYNTAX	TeletexDomainDefinedAttributes
	ACCESS	read-write
	STATUS	mandatory
	::= 6

TeletexDomainDefinedAttributes	::= SEQUENCE SIZE (1..ub-domain-defined-attributes) OF
										TeletexDomainDefinedAttribute

TeletexDomainDefinedAttribute	::= SEQUENCE {
	type	TeletexString (SIZE (1..ub-domain-defined-attribute-type-length)),
	value	TeletexString (SIZE (1..ub-domain-defined-attribute-value-length)) }

pdsNameExtAttribute OBJECT-TYPE	-- EXTENSION-ATTRIBUTE
	SYNTAX	PDSName
	ACCESS	read-write
	STATUS	mandatory
	::= 7

PDSName	::= PrintableString (SIZE (1..ub-pds-name-length))

physicalDeliveryCountryNameExtAttribute OBJECT-TYPE	-- EXTENSION-ATTRIBUTE
	SYNTAX	PhysicalDeliveryCountryName
	ACCESS	read-write
	STATUS	mandatory
	::= 8

PhysicalDeliveryCountryName	::= CHOICE	{
	x121-dcc-code			NumericString (SIZE (ub-country-name-numeric-length)),
	iso-3166-alpha2-code	PrintableString (SIZE (ub-country-name-numeric-length)) }

postalCodeExtAttribute OBJECT-TYPE	-- EXTENSION-ATTRIBUTE
	SYNTAX	PostalCode
	ACCESS	read-write
	STATUS	mandatory
	::= 9

PostalCode	::= CHOICE {
	numericCode		NumericString (SIZE (1..ub-postal-code-length)),
	printableCode	PrintableString (SIZE (1..ub-postal-code-length))  }

physicalDeliveryOfficeNameExtAttribute OBJECT-TYPE	-- EXTENSION-ATTRIBUTE
	SYNTAX	PhysicalDeliveryOfficeName
	ACCESS	read-write
	STATUS	mandatory
	::= 10

PhysicalDeliveryOfficeName	::= PDSParameter

physicalDeliveryOfficeNumberExtAttribute OBJECT-TYPE	-- EXTENSION-ATTRIBUTE
	SYNTAX	PhysicalDeliveryOfficeNumber
	ACCESS	read-write
	STATUS	mandatory
	::= 11

PhysicalDeliveryOfficeNumber	::= PDSParameter

extensionORAddressComponentsExtAttribute OBJECT-TYPE	-- EXTENSION-ATTRIBUTE
	SYNTAX	ExtensionORAddressComponents
	ACCESS	read-write
	STATUS	mandatory
	::= 12

ExtensionORAddressComponents	::= PDSParameter

physicalDeliveryPersonalNameExtAttribute OBJECT-TYPE	-- EXTENSION-ATTRIBUTE
	SYNTAX	PhysicalDeliveryPersonalName
	ACCESS	read-write
	STATUS	mandatory
	::= 13

PhysicalDeliveryPersonalName	::= PDSParameter

physicalDeliveryOrganizationNameExtAttribute OBJECT-TYPE	-- EXTENSION-ATTRIBUTE
	SYNTAX	PhysicalDeliveryOrganizationName
	ACCESS	read-write
	STATUS	mandatory
	::= 14

PhysicalDeliveryOrganizationName	::= PDSParameter

extensionPhysicalDeliveryAddressComponentsExtAttribute OBJECT-TYPE	-- EXTENSION-ATTRIBUTE
	SYNTAX	ExtensionPhysicalDeliveryAddressComponents
	ACCESS	read-write
	STATUS	mandatory
	::= 15

ExtensionPhysicalDeliveryAddressComponents	::= PDSParameter

unformattedPostalAddressExtAttribute OBJECT-TYPE	-- EXTENSION-ATTRIBUTE
	SYNTAX	UnformattedPostalAddress
	ACCESS	read-write
	STATUS	mandatory
	::= 16

UnformattedPostalAddress	::= SET {
	printableAddress	SEQUENCE SIZE(1..ub-pds-physical-address-lines) OF 
				PrintableString (SIZE (1..ub-pds-parameter-length)) OPTIONAL,
	teletexString		TeletexString (SIZE (1..ub-unformatted-address-length)) OPTIONAL }

streetAddressExtAttribute OBJECT-TYPE	-- EXTENSION-ATTRIBUTE
	SYNTAX	StreetAddress
	ACCESS	read-write
	STATUS	mandatory
	::= 17

StreetAddress	::= PDSParameter

postOfficeBoxAddressExtAttribute OBJECT-TYPE	-- EXTENSION-ATTRIBUTE
	SYNTAX	PostOfficeBoxAddress
	ACCESS	read-write
	STATUS	mandatory
	::= 18

PostOfficeBoxAddress	::= PDSParameter

posteRestanteAddressExtAttribute OBJECT-TYPE	-- EXTENSION-ATTRIBUTE
	SYNTAX	PosteRestanteAddress
	ACCESS	read-write
	STATUS	mandatory
	::= 19

PosteRestanteAddress	::= PDSParameter

uniquePostalNameExtAttribute OBJECT-TYPE	-- EXTENSION-ATTRIBUTE
	SYNTAX	UniquePostalName
	ACCESS	read-write
	STATUS	mandatory
	::= 20

UniquePostalName	::= PDSParameter

localPostalAttributesExtAttribute OBJECT-TYPE	-- EXTENSION-ATTRIBUTE
	SYNTAX	LocalPostalAttributes
	ACCESS	read-write
	STATUS	mandatory
	::= 21

LocalPostalAttributes	::= PDSParameter

PDSParameter	::= SET {
	printableString		PrintableString (SIZE (1..ub-pds-parameter-length)) OPTIONAL,
	teletexString		TeletexString (SIZE (1..ub-pds-parameter-length)) OPTIONAL }

extendedNetworkAddressExtAttribute OBJECT-TYPE	-- EXTENSION-ATTRIBUTE
	SYNTAX	ExtendedNetworkAddress
	ACCESS	read-write
	STATUS	mandatory
	::= 22

ExtendedNetworkAddress	::= CHOICE {
	e1634Address	SEQUENCE  {
			number 		[0]	NumericString (SIZE (1..ub-e163-4-number-length)),
			subAddress	[1]	NumericString (SIZE (1..ub-e163-4-sub-address-length ))
							OPTIONAL  },
	psapAddress		[0]	PresentationAddress }

terminalTypeExtAttribute OBJECT-TYPE	-- EXTENSION-ATTRIBUTE
	SYNTAX	TerminalType
	ACCESS	read-write
	STATUS	mandatory
	::= 23

TerminalType  ::=  INTEGER {
	telex		(3),
	teletex 	(4),
	g3Facsimile	(5),
	g4Facsimile	(6),
	ia5Terminal	(7),
	videotex 	(8)  } (SIZE (0..ub-integer-options))

-- Upper bounds
-- from MTSUpperBounds
ub-integer-options							INTEGER	::=	256
ub-x121-address-length						INTEGER	::=	15
ub-country-name-numeric-length				INTEGER	::=	3
ub-country-name-alpha-length				INTEGER	::=	2
ub-domain-name-length						INTEGER	::=	16
ub-terminal-id-length						INTEGER	::=	24
ub-organization-name-length					INTEGER	::=	64
ub-numeric-user-id-length					INTEGER	::=	32
ub-surname-length							INTEGER	::=	40
ub-given-name-length						INTEGER	::=	16
ub-initials-length							INTEGER	::=	5
ub-generation-qualifier-length				INTEGER	::=	3
ub-organizational-units						INTEGER	::=	4
ub-organizational-unit-name-length			INTEGER	::=	32
ub-domain-defined-attributes				INTEGER	::=	4
ub-domain-defined-attribute-type-length		INTEGER	::=	8
ub-domain-defined-attribute-value-length	INTEGER	::=	128
ub-extension-attributes						INTEGER	::=	256
ub-common-name-length						INTEGER	::=	64
ub-pds-name-length							INTEGER	::=	16
ub-postal-code-length						INTEGER	::=	16
ub-pds-parameter-length						INTEGER	::=	30
ub-pds-physical-address-lines				INTEGER	::=	6
ub-unformatted-address-length				INTEGER	::=	180
ub-e163-4-number-length						INTEGER	::=	15
ub-e163-4-sub-address-length				INTEGER	::=	40

END
