-- file: .../asn1specs/p_rec.asn1
--
-- this file is used in ../c{,++}-examples/simple/
--
-- $Header: /baseline/SNACC/asn1specs/p-rec.asn1,v 1.2 2003/12/17 19:05:03 gronej Exp $
-- $Log: p-rec.asn1,v $
-- Revision 1.2  2003/12/17 19:05:03  gronej
-- SNACC baseline merged with PER v1_7 tag
--
-- Revision 1.1.2.1  2003/11/05 14:58:53  gronej
-- working PER code merged with esnacc_1_6
--
-- Revision 1.1.1.1  2000/08/21 20:36:15  leonberp
-- First CVS Version of SNACC.
--
-- Revision 1.3  1997/09/16 14:55:30  wan
-- Added test for "tag dividable by 128" case.
--
-- Revision 1.2  1995/07/25 19:53:17  rj
-- changed `_' to `-' in file names.
--
-- Revision 1.1  1994/08/31  23:05:47  rj
-- first check-in.
--

P-REC DEFINITIONS ::=
BEGIN

PersonnelRecord ::= --snacc isPdu:"TRUE" -- [APPLICATION 0] IMPLICIT SET
{
    name             Name,
    title        [0] IA5String,
    employeeNumber   EmployeeNumber,
    dateOfHire   [1] Date,
    nameOfSpouse [2] Name,
    children     [3] IMPLICIT SEQUENCE OF ChildInformation DEFAULT {}
}

ChildInformation ::= SET
{
    name            Name,
    dateOfBirth [0] Date
}

Name ::= [APPLICATION 1] IMPLICIT SEQUENCE
{
    givenName  IA5String,
    initial    IA5String,
    familyName IA5String
}

EmployeeNumber ::= [APPLICATION 128] IMPLICIT INTEGER

Date ::= [APPLICATION 3] IMPLICIT IA5String -- YYYYMMDD

-- Suggested simple encoding test
PDU1 ::= --snacc isPdu:"TRUE" -- SEQUENCE
{
    height INTEGER(0..255),
    width INTEGER(0..255)
}

END
