ASN-USEFUL DEFINITIONS ::=
BEGIN

-- file: .../asn1specs/asn-useful.asn1
--
-- NOTE: every one of these types is marked as a PDU so the compiler
--       will produce the encode and decode routines that
--       enc/dec the top tag/len pairs, not just the content decoders.
--       (only nec for re-generating the library files "asn_useful.[ch]").
--       The isPdu field does not affect how this module is linked
--       with other modules during compilation.
--
--  (type DEF comment directives immediately follow the "::=")
--
-- MS 92
--
-- $Header: /baseline/SNACC/c++-lib/asn-useful.asn1,v 1.1.1.1 2000/08/21 20:36:08 leonberp Exp $
-- $Log: asn-useful.asn1,v $
-- Revision 1.1.1.1  2000/08/21 20:36:08  leonberp
-- First CVS Version of SNACC.
--
-- Revision 1.3  1995/07/24 15:12:35  rj
-- useful.asn1 renamed to asn-useful.asn1 to accomodate to snacc's new file name generation scheme.
--
-- Revision 1.2  1994/08/28  09:54:19  rj
-- comment leader fixed.
--
-- Revision 1.1  1994/08/28  09:51:15  rj
-- first check-in.


ObjectDescriptor ::= -- isPdu:"TRUE" --
                     [UNIVERSAL 7] IMPLICIT OCTET STRING

NumericString    ::= --snacc isPdu:"TRUE" --
                     [UNIVERSAL 18] IMPLICIT OCTET STRING

PrintableString  ::= --snacc isPdu:"TRUE" --
                     [UNIVERSAL 19] IMPLICIT OCTET STRING

TeletexString    ::= --snacc isPdu:"TRUE" --
                     [UNIVERSAL 20] IMPLICIT OCTET STRING

T61String        ::= --snacc isPdu:"TRUE" --
                     [UNIVERSAL 20] IMPLICIT OCTET STRING

VideotexString   ::= --snacc isPdu:"TRUE" --
                     [UNIVERSAL 21] IMPLICIT OCTET STRING

IA5String        ::= --snacc isPdu:"TRUE" --
                     [UNIVERSAL 22] IMPLICIT OCTET STRING

GraphicString    ::= --snacc isPdu:"TRUE" --
                     [UNIVERSAL 25] IMPLICIT OCTET STRING

VisibleString    ::= --snacc isPdu:"TRUE" --
                     [UNIVERSAL 26] IMPLICIT OCTET STRING

ISO646String     ::= --snacc isPdu:"TRUE" --
                     [UNIVERSAL 26] IMPLICIT OCTET STRING

GeneralString    ::= --snacc isPdu:"TRUE" --
                     [UNIVERSAL 27] IMPLICIT OCTET STRING

UTCTime          ::= --snacc isPdu:"TRUE" --
                     [UNIVERSAL 23] IMPLICIT OCTET STRING

GeneralizedTime  ::= --snacc isPdu:"TRUE" --
                     [UNIVERSAL 24] IMPLICIT OCTET STRING


EXTERNAL         ::= --snacc isPdu:"TRUE" -- [UNIVERSAL 8] IMPLICIT SEQUENCE
{
        direct-reference      OBJECT IDENTIFIER OPTIONAL,
        indirect-reference    INTEGER OPTIONAL,
        data-value-descriptor ObjectDescriptor OPTIONAL,
        encoding CHOICE
        {
                single-ASN1-type [0] OCTET STRING,  -- should be ANY
                octet-aligned    [1] IMPLICIT OCTET STRING,
                arbitrary        [2] IMPLICIT BIT STRING
        }
}

-- new UNIVERSAL types --

UniversalString	::= --snacc isPdu:"TRUE" -- [UNIVERSAL 28] IMPLICIT OCTET STRING

BMPString		::= --snacc isPdu:"TRUE" -- [UNIVERSAL 30] IMPLICIT OCTET STRING


END  -- of ASN-USEFUL  type definitions
